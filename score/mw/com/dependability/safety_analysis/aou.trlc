/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

/* broken_link_c/issue/5834990 */
ScoreReq.AoU MonotonicSemiDynamicMemoryAllocation {
    description = "It shall be ensured that enough memory is configured for shared memory instances, in order that LoLa can perform all necessary allocations (e.g. push-back on a Vector)."
    safety = ScoreReq.Asil.B
    note = "LoLa implements a Monotonic Memory Resource. Once memory is claimed, there is no possibility to release it. LoLa pre-allocates a memory pool, only within this memory pool the monotonic allocations will happen."
    version = 1
    mitigates = "TooMuchMemoryAllocated"
}

/* broken_link_c/issue/5835013 */
ScoreReq.AoU CorrectlyConfiguredMaximumNumberOfSubscriber {
    description = "It shall be ensured that correct maximum number of subscriber is configured for each event for each service instance."
    safety = ScoreReq.Asil.B
    note = "The maximum number of subscriber is used to calculate necessary memory from LoLa side, ensure wait-freedom and ensure data consistency. Without the correct number, none of these guarantees can be given."
    version = 1
    mitigates = "InMemoryConfigurationWrong, TooFewMemoryAllocated, TooMuchMemoryAllocated, SendingEventSendsToWrongConsumer"
}

/* broken_link_c/issue/5835045 */
ScoreReq.AoU CorrectlyConfiguredMaximumNumberOfMaximumElementsPerSubscriber {
    description = "It shall be ensured that correct maximum number of elements per subscriber is configured for each event for each service instance."
    safety = ScoreReq.Asil.B
    note = "The maximum number of elements per subscriber is used to calculate necessary memory from LoLa side, ensure wait-freedom and ensure data consistency. Without the correct number, none of these guarantees can be given."
    version = 1
    mitigates = "InMemoryConfigurationWrong, TooFewMemoryAllocated, TooMuchMemoryAllocated, SendingEventSendsToWrongConsumer"
}

/* broken_link_c/issue/5835084 */
ScoreReq.AoU CorrectlyConfiguredAsilLevel {
    description = "It shall be ensured that the ASIL Level on process level and per service instance is correctly configured."
    safety = ScoreReq.Asil.B
    note = "The ASIL-Level is used to ensure Freedom from Interference (e.g. by configuring access rights). Without a proper configured level, this cannot be ensured."
    version = 1
    mitigates = "InMemoryConfigurationWrong"
}

/* broken_link_c/issue/5835098 */
ScoreReq.AoU OnlyLoLaSupportedTypes {
    description = "It shall be ensured that only types that are supported by LoLa are transmitted."
    safety = ScoreReq.Asil.B
    note = "Every type T transmitted via LoLa needs to fulfill all the following properties: DefaultConstructible (std::is_default_constructible(T) returns true), CopyAssignable (std::is_copy_assignable(T) == true), are not polymorphic (std::is_polymorphic(T) == false), T doesn't allocate dynamic memory."
    version = 1
    mitigates = "MemoryAllocatedInWrongSection"
}

/* broken_link_c/issue/5835119 */
ScoreReq.AoU NoApisFromImplementationNamespace {
    description = "It shall be ensured that no API calls from the implementation namespace (e.g `impl`) are directly invoked or types from within are directly used."
    safety = ScoreReq.Asil.B
    note = "Certain measurements and maybe implemented around the implementation namespace, while it is theoretically possible to directly use these functions, this could lead to unknown and untested side-effects."
    version = 1
    mitigates = "MisusedApis"
}

/* broken_link_c/issue/5835135 */
ScoreReq.AoU NoGuaranteesForNotifications {
    description = "It shall be ensured that a miss behavior of event notification will not harm a safety goal."
    safety = ScoreReq.Asil.B
    note = "It is not guaranteed that notifications will arrive, neither in which latency this will happen, or if they happen too often or on a wrong event. This is caused by underlying OS/HW safety claims."
    version = 1
    mitigates = "SendingEventOnlyPartiallyNotifiesConsumer"
}

/* broken_link_c/issue/5835150 */
ScoreReq.AoU CheckingForPossibleMessageOverflow {
    description = "It shall be ensured that a message overflow, which results in message loss will not harm a safety goal. If this is not possible, a check for message overflow and necessary actions need to be performed."
    safety = ScoreReq.Asil.B
    note = "A message overflow will take place if the event receiver checks/receives samples on a lower rate, than the event sender produces them. A message overflow/loss can be detected by checking if all reserved slots are full. If that is the case a message loss is possible and thus it needs to be handled as if a message loss has happened."
    version = 1
    mitigates = "CallbackInvokedWithWrongData"
}

/* broken_link_c/issue/5835175 */
ScoreReq.AoU DifferentUserForAsilAndQmProcesses {
    description = "It shall be ensured that processes with a different ASIL shall be executed within different user-ids."
    safety = ScoreReq.Asil.B
    note = "LoLa utilizes operating system ACL mechanisms to ensure Freedom From Interference. If a lower ASIL process is executed with the rights of a higher level one, the Freedom from Interference can no longer be guaranteed."
    version = 1
    mitigates = "CallbackNotInvokedDespiteSamplesAvailable"
}

/* broken_link_c/issue/5835192 */
ScoreReq.AoU ConfigOnASafeFilesystem {
    description = "It shall be ensured that any configuration item that is read at runtime by LoLa is stored on a safety certified filesystem (according to the highest supported safety level)."
    safety = ScoreReq.Asil.B
    note = "The configuration needs to be ensured to be valid and it needs to be ensured that no issue in the filesystem causes configuration issues."
    version = 1
    mitigates = "InMemoryConfigurationWrong"
}

/* broken_link_c/issue/5835198 */
ScoreReq.AoU NoStaticContextSupport {
    description = "It shall be ensured that LoLa is not used within static context within C++."
    safety = ScoreReq.Asil.B
    note = "LoLa uses itself static context within C++. A usage within static context could possibly cause the static (De-)Initialization-Fiasco."
    version = 1
    mitigates = "MisusedApis"
}

/* broken_link_c/issue/5835213 */
ScoreReq.AoU NoGuaranteeInAvailabilityOfServices {
    description = "It shall be ensured that no safety goal is harmed, because a service instance is not found."
    safety = ScoreReq.Asil.B
    note = "LoLa is a Service-Discovery based middleware. In such cases it is possible that a service is not offered. Thus, LoLa cannot give any guarantee that a service will be found."
    version = 1
    mitigates = "CreationOfSkeletonNotPossible, WrongStartfindserviceIsStopped"
}

/* broken_link_c/issue/5835249 */
ScoreReq.AoU NoNotificationOnTerminationOfProducer {
    description = "It shall be ensured that termination (either gracefully or due to a malfunction) of a producer will not lead to a violation of a safety goal."
    safety = ScoreReq.Asil.B
    note = "LoLa provides no mechanism to communicate the termination of an event data producer. It is also possible that a producer suddenly crashes and no events are any longer produced. A supervision can be implemented on application side, if events are polled in a certain interval. If no new events are present within a certain set of intervals, it can be assumed that the producer is malfunctioning."
    version = 1
    mitigates = "ServiceOfferingNotStopped, WrongStartfindserviceIsStopped"
}

/* broken_link_c/issue/5835311 */
ScoreReq.AoU CheckForNullptrOnAllocate {
    description = "It shall be checked if Allocate() on an event will return a nullptr. If a nullptr is returned, the system shall transition to safe state."
    safety = ScoreReq.Asil.B
    note = "A nullptr indicates in this case a non-recoverable error and indicates further an issue in the memory control."
    version = 1
    mitigates = "TooFewMemoryAllocated"
}

/* broken_link_c/issue/5835317 */
ScoreReq.AoU OneProducerOnlyOneAllocateePtr {
    description = "It shall be ensured that at any time a producer instance per event only holds one AllocateePtr."
    safety = ScoreReq.Asil.B
    note = "LoLa does not support multi-producer pattern."
    version = 1
    mitigates = "TooFewMemoryAllocated, TooMuchMemoryAllocated, SendingEventSendsToWrongConsumer"
}

/* broken_link_c/issue/5835324 */
ScoreReq.AoU NoCopySendWhileHoldingAllocateePtr {
    description = "It shall be ensured that Send(const& value) is not invoked while an AllocateePtr is held."
    safety = ScoreReq.Asil.B
    note = "Send(const& value) creates an AllocateePtr in its implementation. Thus we would harm the previously stated AoU that only one AllocateePtr is held at any point in time."
    version = 1
    mitigates = ""
}

/* broken_link_c/issue/5835328 */
ScoreReq.AoU NoneReentrantMethodsPerEventInstance {
    description = "It shall be ensured that any LoLa API that is bound to a specific event instance is not called in a reentrant manner."
    safety = ScoreReq.Asil.B
    note = "Thread-Safety is ensured for static methods and over instances."
    version = 1
    mitigates = "FunctionCalledFromMultipleThreads"
}

/* broken_link_c/issue/5835337 */
ScoreReq.AoU SkeletonAliveWhileItsAllocateePtrBeingUsed {
    description = "It shall be ensured that a Skeleton instance is still alive while any AllocateePtr returned by it is used."
    safety = ScoreReq.Asil.B
    note = "A destruction of a Skeleton will invalidate the memory that the AllocateePtr is pointing to."
    version = 1
    mitigates = "ReturnsWrongData"
}

/* broken_link_c/issue/5835346 */
ScoreReq.AoU EventSubscriptionActiveWhileHoldingSamplePtr {
    description = "It shall be ensured that Unsubscribe() isn't called on a proxy event instance as long as any SamplePtr provided by it, is still held. Also the corresponding proxy instance shall be kept alive as on destruction it would implicitly call Unsubscribe()."
    safety = ScoreReq.Asil.B
    note = "Unsubscription of the proxy event will invalidate the memory that the SamplePtr is pointing to."
    version = 1
    mitigates = "ReturnsWrongData, CallbackInvokedWithWrongData"
}

/* broken_link_c/issue/5835351 */
ScoreReq.AoU NoneTerminatingCallbacks {
    description = "It shall be ensured that any callback passed to LoLa for invocation is not throwing."
    safety = ScoreReq.Asil.B
    note = "The behavior is undefined if a callback is throwing."
    version = 1
    mitigates = "MisusedApis"
}

/* broken_link_c/issue/5835363 */
ScoreReq.AoU ValidCallbacksWhileProxyAlive {
    description = "It shall be ensured that all callbacks passed towards LoLa are valid as long as the associated proxy is alive."
    safety = ScoreReq.Asil.B
    note = "While a proxy is alive, it is possible that mentioned callbacks are invoked. If a callback contains for example a dangling reference or pointer, the correct execution cannot be ensured."
    version = 1
    mitigates = "CallbackInvokedWithWrongData"
}

/* broken_link_c/issue/5835376 */
ScoreReq.AoU QualityOfDataIsDependentOnProducer {
    description = "It shall be ensured that the necessary quality of data is produced by the respective skeleton process."
    safety = ScoreReq.Asil.B
    note = "LoLa doesn't do ANY checks on the transmitted data. LoLa provides any data ASIL transparent. Meaning, it neither degrades the ASIL-Level nor does it perform any additional checks to enhance it."
    version = 1
    mitigates = "CallbackInvokedWithWrongData"
}

/* broken_link_c/issue/5835388 */
ScoreReq.AoU ValidityOfPointerOnLoLaPointer {
    description = "It shall be ensured that no pointer, pointing to the memory of a SamplePtr or AllocateePtr is used once the SamplePtr or AllocateePtr are invalid."
    safety = ScoreReq.Asil.B
    note = "Issue: Once the smart-pointers are invalid their respective memory is unmanaged and any access leads to undefined behavior."
    version = 1
    mitigates = "ReturnsWrongData"
}

/* broken_link_c/issue/5835398 */
ScoreReq.AoU LoLaMemoryOnlyAccessedThroughLoLa {
    description = "It shall be ensured that no other code accesses the mapped memory managed by LoLa."
    safety = ScoreReq.Asil.B
    note = "A static mapping of memory or a wild access of heap memory causes undefined behavior."
    version = 1
    mitigates = "MemoryAllocatedInWrongSection"
}

/* broken_link_c/issue/5835403 */
ScoreReq.AoU NoSharedMemoryAllocationInNamespaceLola {
    description = "It shall be ensured that no other code creates shared memory segments beginning with \"lola\"."
    safety = ScoreReq.Asil.B
    note = "Certain contracts are based on the shared memory segment naming, these might get influenced by other code segments using this prefix."
    version = 1
    mitigates = "MemoryAllocatedInWrongSection"
}

/* broken_link_c/issue/5835421 */
ScoreReq.AoU OnlyQnx71Supported {
    description = "It shall be ensured that any application containing LoLa is only executed on QNX Safe Operating System 7.1."
    safety = ScoreReq.Asil.B
    note = "All safety guarantees only hold as long executed on a safe operating system."
    version = 1
    mitigates = "MemoryAllocatedInWrongSection"
}

/* broken_link_c/issue/5835427 */
ScoreReq.AoU LoLaSpecificQnxMessagingEndPointsOnlyAccessedThroughLoLa {
    description = "It shall be ensured that the LoLa specific QNX Message Passing end-points are only accessed through LoLa APIs."
    safety = ScoreReq.Asil.B
    note = "Any influence from other parts of the code might destroy expected contracts. The LoLa specific QNX Message Passing endpoints are located under: /mw_com/message_passing/LoLa_*"
    version = 1
    mitigates = "SendingEventOnlyPartiallyNotifiesConsumer"
}

/* broken_link_c/issue/5835432 */
ScoreReq.AoU AragenNotSafe {
    description = "Input artifacts shall be manually reviewed for correctness"
    safety = ScoreReq.Asil.B
    note = "aragen is not safety qualified, thus its outputs are not safe also. Usage of aragen is not mandatory as the LoLa specific interfaces can be written manually in C++ using LoLa provided support templates."
    version = 1
    mitigates = "GeneratedCodeDoesNotMatchGenerationInputs"
}

/* broken_link_c/issue/5835457 */
ScoreReq.AoU UnsupportedDataTypes {
    description = "It shall be ensured that neither variants nor maps are sent via LoLa."
    safety = ScoreReq.Asil.B
    note = "LoLa theoretically supports these data-types, but they were not subject to audit and extensive testing."
    version = 1
    mitigates = "MemoryAllocatedInWrongSection"
}

/* broken_link_c/issue/6346567 */
ScoreReq.AoU NoGuaranteeOnExecutionTime {
    description = "There is no guarantee on the execution time of any function call provided by LoLa."
    safety = ScoreReq.Asil.B
    note = "This implies that safety-relevant code, where the safety goal is dependent on timing, needs to be supervised."
    version = 1
    mitigates = "AnyFunctionBlocksLongerThanExpected"
}

/* broken_link_c/issue/7091801 */
ScoreReq.AoU UsageOfConfigurationOversubscription {
    description = "If event instance \"oversubscription\" is enabled, LoLa makes no warranty that proxies/consumers can't suffer from data loss! It is the responsibility of the user to adapt scheduling/event-data access in a way that no data-loss happens."
    safety = ScoreReq.Asil.B
    note = "However, we can give the guarantee that if only QM consumers misbehave, ASIL consumers are not affected by these actions. The latter statement enables that a QM application where the scheduling/event-data access is not ensured, will not interfere the ASIL communication. The only thing that could happen is that the QM application might access wrong data or receive no data at all, in an error case (e.g. if it holds more samples then expected)."
    version = 1
    mitigates = ""
}

/* broken_link_c/issue/21206172 */
ScoreReq.AoU SameCompilerSettingsForProviderAndConsumerSide {
    description = "All compiler settings having influence on the binary representation of data exchanged via {{mw::com}}/{{LoLa}} (event, field, service-method payloads) have to be identical for compilation of code containing {{mw::com}} proxies and skeletons, which communicate."
    safety = ScoreReq.Asil.B
    version = 1
    mitigates = ""
}

/* broken_link_c/issue/21209491 */
ScoreReq.AoU EventOrFieldReceptionViaGenericProxyNeedsSpecificCare {
    description = "When receiving event or field data via untyped {{GenericProxyEvent}} or {{GenericProxyField}}, care has to be taken when accessing the corresponding {{SamplePtr<void>}} delivered by calls to {{GetNewSamples()}}: When casting it to the expected type, it needs to be checked that no access behind the size returned by {{GetSampleSize()}} will happen."
    safety = ScoreReq.Asil.B
    version = 1
    mitigates = ""
}

/* broken_link_c/issue/32388804 */
ScoreReq.AoU CorrectlyConfiguredEventsFieldsPerServiceType {
    description = "It shall be ensured that all safety relevant events/fields in the service type are the same in all configurations."
    safety = ScoreReq.Asil.B
    version = 1
    mitigates = "MapContainingNonexistentEvents, IncompleteMapOfEvents"
}

/* added for method FMEA */

ScoreReq.AoU NoGuaranteesForTimelyMethodCallExecution {
    description = "It shall be ensured that a blocking method call will not harm a safety goal."
    safety = ScoreReq.Asil.B
    note = "It is not guaranteed that a method call initiated by the caller will arrive at the callee, neither in which latency this will happen. It is also not guaranteed, that the completion of the call is notified to the caller at all, neither in which latency this will happen. This is caused by underlying OS/HW safety claims - see also [NoGuaranteesForNotifications]. The runtime of a user-provided method-handler is not supervised at all."
    version = 1
    mitigates = "Communication.CallBlocksOnCaller, Communication.CallBlocksOnCallee, Communication.CallBlocksOnUserHandler"
}

/* @ToDo - this is not an AoU but a PreventiveMeasure: Update, when our schema supports this differentiation */
ScoreReq.AoU MethodInArgPtrMatches {
    description = "It shall be ensured that the memory locations of the method call in-arguments provided at the caller side are exactly the same as the memory locations as used at the callee side."
    safety = ScoreReq.Asil.B
    note = "It is not guaranteed that a method call initiated by the caller will arrive at the callee, neither in which latency this will happen. It is also not guaranteed, that the completion of the call is notified to the caller at all, neither in which latency this will happen. This is caused by underlying OS/HW safety claims - see also [NoGuaranteesForNotifications]."
    version = 1
    mitigates = "Communication.CallBlocksOnCaller, Communication.CallBlocksOnCallee, Communication.CallBlocksOnUserHandler"
}

/* broken_link_c/issue/79416086 */
ScoreReq.AoU NoGuaranteeOnSubscriptionStateCorrectness {
    description = "For safety critical use cases, an application must treat a SubscriptionState of kSubscribed or kSubscriptionPending (returned by GetSubscriptionState() or reported by the SubscriptionStateChangeHandler) as the same."
    safety = ScoreReq.Asil.B
    note = "On a technical level, kSubscribed and kSubscriptionPending cannot be reliably differentiated, see {{SubscriptionState}} Component requirement for more details"
    version = 1
}

/* E2E error handling */

ScoreReq.AoU E2EMethodCallsNotNecessarilyPeriodic {
    description = "It shall be ensured that a safety goal is not violated solely because an E2E-protected method call/request is not invoked periodically."
    safety = ScoreReq.Asil.B
    note = "Unlike event communication, method requests are issued on-demand and have no inherent cycle time. E2E cannot reliably detect loss or delay of a request that has no periodic expectation."
    version = 1
    mitigates = "ApplicationMisinterpretsE2ECheckResult"
}

ScoreReq.AoU ApplicationMustWaitForValidStateDuringInitialization {
    description = "It shall be ensured that safety-relevant use of a sample waits for the E2E state machine to reach a valid state before an initialization-phase check result is treated as a fully-qualified valid result."
    safety = ScoreReq.Asil.B
    note = "The initialization condition exists to signal 'not enough history yet', not 'confirmed good'; an application that proceeds as if this were a normal valid result loses the qualification guarantee the warm-up window is meant to provide."
    version = 1
    mitigates = "ApplicationMisinterpretsE2ECheckResult"
}

ScoreReq.AoU ApplicationMustTreatNoNewDataAsUntrustworthy {
    description = "It shall be ensured that safety-relevant use of a sample treats a no-new-data E2E check result as the absence of a trustworthy sample rather than an implicit pass."
    safety = ScoreReq.Asil.B
    note = "A no-new-data result signals only that no fresh sample was available for this check, not that the previous sample remains valid; an application that proceeds as if this were a normal valid result loses the qualification guarantee E2E is meant to provide."
    version = 1
    mitigates = "ApplicationMisinterpretsE2ECheckResult"
}

ScoreReq.AoU DataIdsGloballyUniqueForE2EProtectedElements {
    description = "It shall be ensured that the Data ID (or Data ID list) configured for each E2E-protected event, field, or method is unique across the whole system of communicating processes."
    safety = ScoreReq.Asil.B
    note = "Data ID uniqueness is only a recommendation rather than a structurally mandated constraint; if two protected elements share a Data ID, masquerading detection is weakened because the receiver has less identity information to distinguish one protected message from another."
    version = 1
    mitigates = "ApplicationMisinterpretsE2ECheckResult"
}
